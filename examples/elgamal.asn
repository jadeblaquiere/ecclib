--BSD 3-Clause License
--
--Copyright (c) 2018, jadeblaquiere
--All rights reserved.
--
--Redistribution and use in source and binary forms, with or without
--modification, are permitted provided that the following conditions are met:
--
--* Redistributions of source code must retain the above copyright notice, this
--  list of conditions and the following disclaimer.
--
--* Redistributions in binary form must reproduce the above copyright notice,
--  this list of conditions and the following disclaimer in the documentation
--  and/or other materials provided with the distribution.
--
--* Neither the name of the copyright holder nor the names of its
--  contributors may be used to endorse or promote products derived from
--  this software without specific prior written permission.
--
--THIS SOFTWARE IS PROVIDED BY THE COPYRIGHT HOLDERS AND CONTRIBUTORS "AS IS"
--AND ANY EXPRESS OR IMPLIED WARRANTIES, INCLUDING, BUT NOT LIMITED TO, THE
--IMPLIED WARRANTIES OF MERCHANTABILITY AND FITNESS FOR A PARTICULAR PURPOSE ARE
--DISCLAIMED. IN NO EVENT SHALL THE COPYRIGHT HOLDER OR CONTRIBUTORS BE LIABLE
--FOR ANY DIRECT, INDIRECT, INCIDENTAL, SPECIAL, EXEMPLARY, OR CONSEQUENTIAL
--DAMAGES (INCLUDING, BUT NOT LIMITED TO, PROCUREMENT OF SUBSTITUTE GOODS OR
--SERVICES; LOSS OF USE, DATA, OR PROFITS; OR BUSINESS INTERRUPTION) HOWEVER
--CAUSED AND ON ANY THEORY OF LIABILITY, WHETHER IN CONTRACT, STRICT LIABILITY,
--OR TORT (INCLUDING NEGLIGENCE OR OTHERWISE) ARISING IN ANY WAY OUT OF THE USE
--OF THIS SOFTWARE, EVEN IF ADVISED OF THE POSSIBILITY OF SUCH DAMAGE.

EGExampleASN DEFINITIONS EXPLICIT TAGS ::=

BEGIN

ECElgamalCiphertxt ::= SEQUENCE {
    c       OCTET STRING,
    d       OCTET STRING,
    curve   EllipticCurve
}

EllipticCurve ::= SEQUENCE {
    p       OCTET STRING,
    type    EllipticCurveType,
    param   CurveParams,
    n       OCTET STRING,
    h       OCTET STRING,
    g       XYPoint,
    bits    INTEGER
}

XYPoint ::= SEQUENCE {
    x   OCTET STRING,
    y   OCTET STRING
}

-- typedef enum {EQTypeNone, EQTypeUninitialized, EQTypeShortWeierstrass, EQTypeEdwards, EQTypeMontgomery, EQTypeTwistedEdwards} _mpECurve_eq_type;
EllipticCurveType ::= ENUMERATED {
    none                (0),
    uninitialized       (1),
    shortWeierstrass    (2),
    edwards             (3),
    montgomery          (4),
    twistedEdwards      (5)
}

CurveParams ::= SEQUENCE {
    p1   OCTET STRING,
    p2   OCTET STRING
}

END
